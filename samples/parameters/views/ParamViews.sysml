package ParamViews {
    private import ParamModel::*;
    private import StandardViewDefinitions::*;

    view 'parameters and values' : GeneralView {
        expose Focus;
        expose Shoot;
        expose Settings;
        expose camera;
    }
}
